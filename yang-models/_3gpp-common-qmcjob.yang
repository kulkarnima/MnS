module _3gpp-common-qmcjob {
  yang-version 1.1;
  namespace "urn:3gpp:sa5:_3gpp-common-qmcjob";
  prefix "qmc3gpp";

  import _3gpp-common-top { prefix top3gpp; }
  import _3gpp-common-subnetwork { prefix subnet3gpp; }
  import _3gpp-common-yang-types { prefix types3gpp; }
  import _3gpp-5g-common-yang-types { prefix types5g3gpp; }
  import _3gpp-common-managed-element { prefix me3gpp; }
 
  import ietf-inet-types { prefix inet; }

  organization "3GPP SA5";
  contact "https://www.3gpp.org/DynaReport/TSG-WG--S5--officials.htm?Itemid=464";

  description "Quality of Experience Measurement Collection Job handling";

  reference "3GPP TS 28.623
      Generic Network Resource Model (NRM)
      Integration Reference Point (IRP);
      Solution Set (SS) definitions

      3GPP TS 28.622
      Generic Network Resource Model (NRM)
      Integration Reference Point (IRP);
      Information Service (IS)";

  revision 2022-08-17 { reference "CR-0185"; }
  revision 2022-04-29 { reference "CR-0171"; }
  revision 2022-03-22 { reference "draftCR"; }
  revision 2022-01-06 { reference "CR-0142"; }
    
  grouping QMCJobGrp {
    leaf serviceType {
      description "Specifies an end user service type for QoE measurements.";
      mandatory true;
      type enumeration {
      enum DASH;
      enum MTSI;
      enum VR;
    }
    }

    leaf areaScope {
      type string;
      description "Defines the area in terms of NR cells or Tracking Area 
        where the QMC shall take place.";
    }

    leaf qoECollectionEntityAddress {
      type inet:ip-address;
      mandatory true;
      description "Specifies the address to which the QMC records shall be
        transferred.  Ipv4 or Ipv6 address(es) may be used.";
    }

    list pLMNTarget {
      max-elements 1;
      description "Defines the PLMN for which sessions shall be selected in 
        the network request session in case of area based QMC when several 
        PLMNs are supported in the RAN (this means that shared cells and not 
        shared cells are allowed for the specified PLMN. Furthermore, several 
        PLMNs can be used for not shared RAN cases as well as for shared RAN 
        cases.). Only the sessions may be selected where the PLMN that the 
        UE reports as selected PLMN is the same as the PLMN Target.";
      uses types3gpp:PLMNId;
      key "mcc mnc";
    }

    leaf qoETarget {
      type string;
      description "Specifies the target object of the QMC in case of 
        signalling based QMC.  The qoETarget attribute shall be able 
        to carry IMSI or SUPI.";
      mandatory true;
    }

    leaf qoEReference {
      type string;
      mandatory true;
      description "Identifies the QoE measurement collection job in the 
        Managed Elements and in the measurement collection entity.  The QoE
        reference shall be globally unique therefore it is composed as follows:
        MCC+MNC+QMC ID, where the MCC and MNC are coming with the QMC 
        activation request from the management system to identify one PLMN 
        containing the management system, and QMC ID is a 3 byte Octet String. 
        The QMC ID is generated by the management system or the operator.";
    }

    list sliceScope {
      description "Contains a list of S-NSSAIs (Single Network Slice Selection
        Assistance Information).  A Network Slice end to end is identified by
        S-NSSAI.";
      key "sd sst";
      uses types5g3gpp:SNssai;
    }

    leaf qMCConfigFile {
      type string;
      description "Provides a reference to a file including the parameters for 
        configuration of application layer measurements, known as Container
        for Application Layer Measurement Configuration.";
      mandatory true;
    }
  }
    
   grouping QMCJobSubTree {
   description "Helps with augmenting QMCJob into multple places.";
    list QMCJob {
      description "Represents the QMCJob IOC.";
      key id;
      uses top3gpp:Top_Grp;
      container attributes {
        uses QMCJobGrp;
      }
    }
  }
  
   augment "/subnet3gpp:SubNetwork" {
        uses QMCJobSubTree;
   }

   augment "/me3gpp:ManagedElement" {
        uses QMCJobSubTree;
   }
}
