module _3gpp-nr-nrm-gnbdufunction {
  yang-version 1.1;
  namespace "urn:3gpp:sa5:_3gpp-nr-nrm-gnbdufunction";
  prefix "gnbdu3gpp";

  import _3gpp-common-managed-function { prefix mf3gpp; }
  import _3gpp-common-managed-element { prefix me3gpp; }
  import _3gpp-common-top { prefix top3gpp; }
  import _3gpp-common-yang-types { prefix types3gpp; }

  organization "3GPP SA5";
  contact "https://www.3gpp.org/DynaReport/TSG-WG--S5--officials.htm?Itemid=464";
  description "Defines the YANG mapping of the GNBDUFunction Information
    Object Class (IOC) that is part of the NR Network Resource Model (NRM).";
  reference "3GPP TS 28.541 5G Network Resource Model (NRM)";

  revision 2022-07-28 { reference "CR-18-541-yang-corrections"; }
  revision 2021-10-28 { reference CR-0607 ; }
  revision 2021-04-30 { reference CR-0490 ; }
  revision 2020-10-02 { reference CR-0384 ; }
  revision 2020-03-12 { reference "SP-200233 S5-201547" ; }
  revision 2020-02-14 { reference S5-20XXXX ; }
  revision 2019-10-28 { reference S5-193518 ; }
  revision 2019-08-21 {reference "Initial revision."; }

  feature DRACHOptimizationFunction {
    description "Class representing D-SON function of RACH optimization
      feature";
  }

  grouping RimRSReportInfoGrp {
    description "This  data type defines necessary reporting information
      derived from the detected RIM-RS, including
      1)  The detected set ID;
      2)  Propagation delay in number of OFDM symbols
      3)  Functionality of the RS (RS-1 or RS-2, Enough or Not enough
        mitigation for RS-1).

      RS-1 is equivalent to RIM-RS type 1 (see 38.211, subclause 7.4.1.6).
      RS-2 is equivalent to RIM-RS type 2 (see 38.211, subclause 7.4.1.6).
        Enough mitigation for RS-1 means 'Enough' / 'Not enough' indication
          functionality is enabled for RIM RS-1 and RIM-RS type 1 is used to
          indicate 'enough mitigation' functionality.
        Not enough mitigation for RS-1 means 'Enough' / 'Not enough' indication
          functionality is enabled for RIM RS-1 and RIM-RS type 1 is used to
          indicate 'Not enough mitigation' functionality.";

    leaf detectedSetID {
      type uint32 ;
      description "Set ID of the detected RIM-RS
        allowedValues: 0,1...max{totalnrofSetIdofRS1, totalnrofSetIdofRS2}";
    }

    leaf propagationDelay {
      type uint32 ;
      must '. <= ../../maxPropagationDelay' {
        error-message "allowedValues: 0, 1.. maxPropagationDelay";
      }
      description "This attribute indicates the propagation delay of the
        detected RIM-RS, in number of OFDM symbol.";
    }

    leaf functionalityOfRIMRS {
      type enumeration {
        enum RS1;
        enum RS2;
        enum RS1_FOR_ENOUGH_MITIGATION;
        enum RS1_FOR_NOT_ENOUGH_MITIGATION;
      }
      mandatory true;
      description "Indicates the functionality of the detected RIM-RS.
        If the indication of enableEnoughNotEnoughIndication is 'enabled',
          valid values are {RS2, RS1forEnoughMitigation,
          RS1forNotEnoughMitigation};
        If the indication of enableEnoughNotEnoughIndication is 'disabled',
          valid values are {RS1, RS2}.

        RS1forEnoughMitigation means RIM-RS type 1 is used to indicate
         'enough mitigation' functionality.
        RS1forNotEnoughMitigation means RIM-RS type 1 is used to indicate
          'Not enough mitigation' functionality.";
    }
  }

  grouping RimRSReportConfGrp {
    description "Defines RIM-RS reporting configuration";

    leaf reportIndicator {
      type types3gpp:EnabledDisabled;
      default DISABLED;
      description "Used to enable or disable the RS report on a gNB.
        If the indication is 'enable', the gNB starts to periodically report
        necessary information derived from the detected RIM-RS to OAM.
        If the indication is 'disable', the gNB stops reporting.";
    }

    leaf reportInterval {
      type uint32;
      mandatory true;
      units ms;
      description "Used to define reporting interval of a gNB in ms.";
    }

    leaf nrofRIMRSReportInfo {
      type uint32;
      mandatory true;
      description "Used to define the maximum number of RIMRSReportInfo in
        a single report.";
    }

    leaf maxPropagationDelay {
      type uint32 {
        range "0..327679";
      }
      mandatory true;
      description "Used to define the maximum reported OFDM symbol number for
        the propagation delay of the detected RIM-RS in each RIMRSReportInfo.

        allowedValues: 0, 1..20**2*maxNrofSymbols-1, where maxNrofSymbols=14.";
    }

    list RimRSReportInfoList {
      key detectedSetID;
      description "Represents a list (the length of the list is
        nrofRIMRSReportInfo) of necessary information derived from the
        detected RIM-RS.";
      uses RimRSReportInfoGrp;
    }
  }

  grouping GNBDUFunctionGrp {
    description "Represents the GNBDUFunction IOC.";
    reference "3GPP TS 28.541";
    uses mf3gpp:ManagedFunctionGrp;

    leaf gNBId {
      type int64 { range "0..4294967295"; }
      mandatory true;
      description "Identifies a gNB within a PLMN. The gNB Identifier (gNB ID)
        is part of the NR Cell Identifier (NCI) of the gNB cells.";
      reference "gNB ID in 3GPP TS 38.300, Global gNB ID in 3GPP TS 38.413";
    }

    leaf gNBIdLength {
      type int32 { range "22..32"; }
      mandatory true;
      description "Indicates the number of bits for encoding the gNB ID.";
      reference "gNB ID in 3GPP TS 38.300, Global gNB ID in 3GPP TS 38.413";
    }

    leaf gNBDUId {
      type int64 { range "0..68719476735"; }
      mandatory true;
      description "Uniquely identifies the DU at least within a gNB.";
      reference "3GPP TS 38.473";
    }

    leaf gNBDUName {
      type string { length "1..150"; }
      description "Identifies the Distributed Unit of an NR node";
      reference "3GPP TS 38.473";
    }

    list rimRSReportConf {
      key reportInterval;
      config false;
      min-elements 1;
      max-elements 1;
      description "Used to configure gNBs to report the all necessary
        information derived from the detected RIM-RS to OAM.";
      uses RimRSReportConfGrp;
    }
  }

  augment "/me3gpp:ManagedElement" {

    list GNBDUFunction {
   key id;
      description "Represents the logical function DU of gNB or en-gNB.";
      reference "3GPP TS 28.541";
      uses top3gpp:Top_Grp;
      container attributes {
        uses GNBDUFunctionGrp;
      }
      uses mf3gpp:ManagedFunctionContainedClasses;
    }
  }
}
