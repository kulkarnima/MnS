module _3gpp-inv-inventoryunithw {
  yang-version 1.1;
  namespace "urn:3gpp:sa5:_3gpp-inv-inventoryunithw";
  prefix invhw3gpp;

  import ietf-yang-types { prefix yang; }
  import _3gpp-common-yang-types { prefix types3gpp; }
  import _3gpp-common-top { prefix top3gpp; }
  import _3gpp-common-managed-element { prefix me3gpp; }

  organization "3GPP SA5";
  contact "https://www.3gpp.org/DynaReport/TSG-WG--S5--officials.htm?Itemid=464";

  description "This model defines a YANG mapping of the hardware inventory data 
    IOC for Alternative 2 of the IM NRM, TS 28.632.";
  reference "3GPP TS 28.633
     Inventory Management (IM)
     Network Resource Model (NRM)
     Integration Reference Point (IRP);
     Solution Set (SS) definitions
  
     3GPP TS 28.632
     Inventory Management (IM)
     Network Resource Model (NRM)
     Integration Reference Point (IRP);
     Information Service (IS)";

  revision 2021-10-01 { reference "CR-0009"; }

  typedef ManualDataEntry {
    description "Non-extensible enumeration indicating whether a unit is 
      'passive', i.e. only supporting manual data entry, or 'active', i.e. 
      self-reporting";
    type enumeration {
      enum PASSIVE {
        description "Manual insertion of inventory data is needed.";
      }
      enum ACTIVE {
        description "Inventory data can be read from the unit.";
      }
    }
  }

  grouping InventoryUnitHwGrp {
    description "Represents the InventoryUnitHw IOC.";
    leaf hwId {
      description "Hardware identifier allocated by the vendor, e.g. the serial 
        number.";
      type string;
      config false;
    }
    leaf hwType {
      description "Type of the Hardware unit e.g. equipment holder, carriage.";
      type string;
      config false;
    }
    leaf hwName {
      description "Mnemonic of Hardware inventory unit family type (e.g. Fan, 
        PSU) assigned by vendor.";
      type string;
      config false;
    }
    leaf hwVersion {
      description "Version / revision number of current unit e.g. firmware 
        version.";
      type string;
      config false;
    }
    leaf vendorName {
      description "Name of inventory unit vendor (or vendors may provide 
        manufacturer name)";
      type string;
      config false;
    }
    leaf salesUniqueId {
      description "Unique identifier used by vendor (used e.g. for ordering a 
        new unit).";
      type string;
      config false;
    }
    leaf hwUnitLocation {
      description "Unique physical / logical location identifier within NE.";
      type string;
      config false;
    }
    leaf model {
      description "Equipment configuration, e.g. standard hardware unit or a 
        variant that may contain additional disk capacity.";
      type string;
      config false;
    }
    leaf hwCapability {
      description "Hardware capability e.g. capacity, size.";
      type string;
      config false;
    }
    leaf modificationDate {
      description "Date/time stamp of last change (e.g. repair action).";
      type yang:date-and-time;
      config false;
    }
    leaf manualDataEntry {
      description "Indicates whether unit is passive (manual insertion of 
        inventory data is needed) or active (inventory data can be read from 
        the unit).";
      type ManualDataEntry;
      config false;
    }
    leaf additionalInformation {
      description "Supplementary information about inventory data (if any).";
      type string;
      config false;
    }
    
    leaf mFunction {
      description "DN of related ManagedFunction.";
      type types3gpp:DistinguishedName;
      config false;
    }
    leaf-list lICList {
      description "Set of DNs of related InventoryUnitLic IOCs.";
      type types3gpp:DistinguishedName;
      config false;
    }
    leaf-list nEList {
      description "Set of DNs of related InventoryUnitNE IOCs.";
      type types3gpp:DistinguishedName;
      config false;
    }
    leaf-list sWList {
      description "Set of DNs of related InventoryUnitSw IOCs.";
      type types3gpp:DistinguishedName;
      config false;
    }
  }

  augment "/me3gpp:ManagedElement" {
    list InventoryUnitHw {
      uses top3gpp:Top_Grp;
      key id;
      description "Represents the hardware components.";
      container attributes {
        uses InventoryUnitHwGrp;
        
        // Data nodes that follow provide recursive containment
        leaf-list parents {
          type leafref {
            path "../../../InventoryUnitHw/id";
          }
          description
            "Reference to all containing InventoryUnitHw instances in
             strict order from the root down to the immediate
             parent (i.e. the full path from the top level InventoryUnitHw 
             and downward).
             If InventoryUnitHw instances form a containment hierarchy this is
             modeled using references between the child InventoryUnitHws
             and the parent InventoryUnitHw.
             This reference MUST NOT be present for the top level
             InventoryUnitHw and MUST be present for all InventoryUnitHws below 
             it.";
        }
        leaf-list containedChildren {
          type leafref {
            path "../../../InventoryUnitHw/id";
          }
          description
            "Reference to all directly contained InventoryUnitHw instances.
             If InventoryUnitHw instances form a containment hierarchy
             this is modeled using references between the child
             InventoryUnitHws and the parent InventoryUnitHw.";
        }
      }
    }
  }
}
