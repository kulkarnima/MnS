module _3gpp-nr-nrm-operatordu {
  yang-version 1.1;
  namespace "urn:3gpp:sa5:_3gpp-nr-nrm-operatordu";
  prefix "operdu3gpp";

  import _3gpp-common-top { prefix top3gpp; }
  import _3gpp-common-managed-element { prefix me3gpp; }
  import _3gpp-nr-nrm-gnbdufunction {prefix gnbdu3gpp; }

  organization "3GPP SA5";
  contact "https://www.3gpp.org/DynaReport/TSG-WG--S5--officials.htm?Itemid=464";
  description "Defines the YANG mapping of the OperatorDU Information Object
    Class (IOC) that is part of the NR Network Resource Model (NRM).";
  reference "3GPP TS 28.541 5G Network Resource Model (NRM)";

  revision 2021-10-01 { reference "Initial revision"; }

  grouping OperatorDUGrp {
    description "Represents the OperatorDU IOC.";
    reference "3GPP TS 28.541";
    uses gnbdu3gpp:GNBDUFunctionGrp {
      refine gNBId {
        mandatory true;
      }
      refine gNBIdLength {
        mandatory true;
      }
    }
  }

  augment "/me3gpp:ManagedElement/gnbdu3gpp:GNBDUFunction" {

    list OperatorDU {
      description "Contains attributes to support the 5G MOCN network sharing.";
      reference "3GPP TS 28.541";
      key id;
      uses top3gpp:Top_Grp;
      container attributes {
        uses OperatorDUGrp;
      }
      uses gnbdu3gpp:GNBDUFunctionGrp;
    }
  }
}
