module _3gpp-5gc-nrm-pcffunction {
  yang-version 1.1;
  
  namespace urn:3gpp:sa5:_3gpp-5gc-nrm-pcffunction;
  prefix pcf3gpp;
  
  import _3gpp-common-managed-function { prefix mf3gpp; }
  import _3gpp-common-managed-element { prefix me3gpp; }
  import ietf-inet-types { prefix inet; }
  import _3gpp-common-yang-types { prefix types3gpp; }
  import _3gpp-5g-common-yang-types { prefix types5g3gpp; }
  import _3gpp-common-top { prefix top3gpp; }
  
  organization "3gpp SA5";
  contact "https://www.3gpp.org/DynaReport/TSG-WG--S5--officials.htm?Itemid=464";
  description "This IOC represents the PCF function in 5GC. For more 
    information about the PCF, see 3GPP TS 23.501.";
  reference "3GPP TS 28.541";
  
  revision 2020-11-05 { reference CR-0411 ; }
  revision 2020-08-06 { reference "CR-0333"; }
  revision 2020-08-06 { reference "CR-0331"; }
  revision 2019-10-25 { reference "S5-194457 S5-193518"; }
  revision 2019-05-22 { reference "initial revision"; }
  
  grouping PCFFuntionGrp {
    description "Represents the PCFFuntion IOC";
    uses mf3gpp:ManagedFunctionGrp;
    
    list pLMNIdList {
      description "List of at most six entries of PLMN Identifiers, but at 
        least one (the primary PLMN Id).
        The PLMN Identifier is composed of a Mobile Country Code (MCC) and a  
       Mobile Network Code (MNC).";

      min-elements 1;
      max-elements 6;
      key "mcc mnc";
      uses types3gpp:PLMNId;
    }
    
    leaf sBIFQDN {
      description "The FQDN of the registered NF instance in the service-based 
        interface.";
      type inet:domain-name;
    }
    
    list sNSSAIList {
      description "List of S-NSSAIs the managed object is capable of supporting.
                   (Single Network Slice Selection Assistance Information)
                   An S-NSSAI has an SST (Slice/Service type) and an optional SD
                   (Slice Differentiator) field.";
      //optional support
      reference "3GPP TS 23.003";
      key "sd sst";
      uses types5g3gpp:SNssai;
    }
    
    list managedNFProfile {
      key idx;
      min-elements 1;
      max-elements 1;
      uses types3gpp:ManagedNFProfile;
    }
    list commModelList {
      min-elements 1;
      key "groupId";
      description "Specifies a list of commModel. It can be used by NF and 
        NF services to interact with each other in 5G Core network ";
      reference "3GPP TS 23.501";
      uses types5g3gpp:CommModel;
    }
    leaf dynamic5QISetRef {
      type types3gpp:DistinguishedName;
      description "DN of the Dynamic5QISet that the PCFFunction supports 
        (is associated to).";
    }
    leaf configurable5QISetRef {
      type types3gpp:DistinguishedName;
      description "DN of the Configurable5QISet that the PCFFunction supports 
        (is associated to).";
    }
  }
  
  augment "/me3gpp:ManagedElement" {
    list PCFFunction {
      description "5G Core PCF Function";
      reference "3GPP TS 28.541";
      key id;
      uses top3gpp:Top_Grp;
      container attributes {
        uses PCFFuntionGrp;
      }
      uses mf3gpp:ManagedFunctionContainedClasses;
    }
  }
}
