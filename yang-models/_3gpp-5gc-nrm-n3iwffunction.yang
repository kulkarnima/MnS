module _3gpp-5gc-nrm-n3iwffunction {
  yang-version 1.1;
  
  namespace urn:3gpp:sa5:_3gpp-5gc-nrm-n3iwffunction;
  prefix n3iwf3gpp;
  
  import _3gpp-common-managed-function { prefix mf3gpp; }
  import _3gpp-common-managed-element { prefix me3gpp; }
  import _3gpp-common-yang-types { prefix types3gpp; }
  import _3gpp-common-top { prefix top3gpp; }
  
  organization "3gpp SA5";
  description "This IOC represents the N3IWF function which is used to enable non-3GPP
               access networks connected to the 5GC. For more information about the N3IWF, see 3GPP TS 23.501.";
  reference "3GPP TS 28.541";
  
  revision 2019-10-28 { reference S5-193518 ; }
  revision 2019-05-22 {
    description "initial revision";
  }
  
  grouping N3IWFFunctionGrp {
    uses mf3gpp:ManagedFunctionGrp;
    
    list pLMNIdList {
      description "List of at most six entries of PLMN Identifiers, but at least one (the primary PLMN Id).
                   The PLMN Identifier is composed of a Mobile Country Code (MCC) and a Mobile Network Code (MNC).";

      min-elements 1;
      max-elements 6;
      key "mcc mnc";
      uses types3gpp:PLMNId;
    }

    list commModelList {
      min-elements 1;
      key "groupId";
      uses types5g3gpp:CommModel;
    }
  }
  
  augment "/me3gpp:ManagedElement" {
    list N3IWFFunction {
      description "5G Core N3IWF Function";
      reference "3GPP TS 28.541";
      key id;
      uses top3gpp:Top_Grp;
      container attributes {
        uses N3IWFFunctionGrp;
      }
      uses mf3gpp:ManagedFunctionContainedClasses;
    }
  }
}
